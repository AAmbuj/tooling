/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package MyPackage

import ScoreReq

// --- Assumed System Requirement -------------------------------------------
// Root of the traceability chain. Needs a rationale.

ScoreReq.AssumedSystemReq ASR_001 {
    description = "The system shall <observable behaviour expected from the wider platform>"
    safety      = ScoreReq.Asil.B
    rationale   = "<why this system-level requirement exists and how it was derived>"
    version     = 1
}

// --- Feature Requirement ---------------------------------------------------
// Derived from one or more AssumedSystemReq. Allocated to the dependable_element.

ScoreReq.FeatReq FEAT_001 {
    description  = "The :term:`component` shall <single observable, verifiable behaviour>"
    safety       = ScoreReq.Asil.B
    derived_from = [MyPackage.ASR_001@1]
    version      = 1
}

// --- Component Requirement -------------------------------------------------
// Derived from a FeatReq, AssumedSystemReq or received AoU.
// Allocated to exactly one component. Traced to test cases.

ScoreReq.CompReq COMP_001 {
    description  = "<The operation> shall <do exactly one thing> <under which condition>"
    safety       = ScoreReq.Asil.B
    derived_from = [MyPackage.FEAT_001@1]
    version      = 1
}

// --- Assumption of Use -----------------------------------------------------
// A condition the integrator must fulfil. Shipped to consumers of this SEooC.

ScoreReq.AoU AOU_001 {
    description = "The caller shall <condition the integrator must guarantee>"
    safety      = ScoreReq.Asil.B
    version     = 1
}
